// ─── Root Package ──────────────────────────────────────────────
package SmartTemperatureSensor {
    doc /* Smart Temperature Sensor: a VSE demo project for indoor
           climate monitoring. Imports all model domains. */

    import StakeholderNeeds::*;
    import SystemRequirements::*;
    import ElementRequirements::*;
    import Architecture::*;
    import Verification::*;
    import Validation::*;
}

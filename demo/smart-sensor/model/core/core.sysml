// Core package for SmartSensor.
//
// Top-level package per methodology §8.3.1. Imports the demo's
// sub-packages.

package <SS> SmartSensor_Core {

    private import SmartSensor_Stakeholders::*;
    private import SmartSensor_Concerns::*;
    private import SmartSensor_BaseArchitecture::*;
    private import SmartSensor_Context::*;
    private import SmartSensor_Domain::*;

    private import SmartSensor_StakeholderStories::*;
    private import SmartSensor_SystemStories::*;
    private import SmartSensor_UseCases::*;

    private import SmartSensor_InterfaceTypes::*;

    private import SmartSensor_VerificationCases::*;
    private import SmartSensor_ValidationCases::*;
}
